module ietf-ioam-integrity {
  yang-version 1.1;
  namespace "urn:ietf:params:xml:ns:yang:ietf-ioam-integrity";
  prefix "ioam-int";

  import ietf-ioam {
    prefix ioam;
    reference
      "RFC 9617: A YANG Data Model for In Situ Operations,
       Administration, and Maintenance (IOAM)";
  }

  organization
    "IETF IPPM (IP Performance Measurement) Working Group";

  contact
    "WG Web:   <https://datatracker.ietf.org/wg/ippm>
     WG List:  <mailto:ippm@ietf.org>
     Author:   Tianran Zhou
               <mailto:zhoutianran@huawei.com>
     Author:   Justin Iurman
               <mailto:justin.iurman@uliege.be>";

  description
    "This YANG module specifies a vendor-independent data model for
     In Situ Operations, Administration, and Maintenance (IOAM)
     Integrity Protected Options.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2024-08-31 {
    description
      "Initial revision.";
    reference
      "RFC XXXX: A YANG Data Model for In Situ Operations,
       Administration, and Maintenance (IOAM) Integrity Protected
       Options";
  }

  /*
   * FEATURES
   */

  feature int-incremental-trace
  {
    description
      "This feature indicates that the Integrity Protected
       Incremental Trace-Option is supported.";
    reference
      "RFC YYYY: Integrity Protection of In Situ Operations,
       Administration, and Maintenance (IOAM) Data Fields";
  }

  feature int-preallocated-trace
  {
    description
      "This feature indicates that the Integrity Protected
       Pre-allocated Trace-Option is supported.";
    reference
      "RFC YYYY: Integrity Protection of In Situ Operations,
       Administration, and Maintenance (IOAM) Data Fields";
  }

  feature int-proof-of-transit
  {
    description
      "This feature indicates that the Integrity Protected Proof of
       Transit Option is supported.";
    reference
      "RFC YYYY: Integrity Protection of In Situ Operations,
       Administration, and Maintenance (IOAM) Data Fields";
  }

  feature int-edge-to-edge
  {
    description
      "This feature indicates that the Integrity Protected
       Edge-to-Edge Option is supported.";
    reference
      "RFC YYYY: Integrity Protection of In Situ Operations,
       Administration, and Maintenance (IOAM) Data Fields";
  }

  /*
   * IDENTITIES
   */

  identity method {
    description
      "Base identity to represent the Integrity Protection Method.";
  }

  identity method-1 {
    base method;
    description
      "The Integrity Protection Method 1 uses AES-GMAC with a 12-byte
       Nonce and a 16-byte ICV.";
    reference
      "RFC YYYY: Integrity Protection of In Situ Operations,
       Administration, and Maintenance (IOAM) Data Fields";
  }

  /*
   * TYPE DEFINITIONS
   */

  typedef method-type {
    type identityref {
      base method;
    }
    description
      "It specifies the Integrity Protection Method.";
  }

  /*
   * DATA NODES
   */

  augment "/ioam:ioam/ioam:profiles/ioam:profile" {
    description
      "This augmentation adds 4 profiles for the Integrity Protected
       Options.";

    container int-incremental-tracing-profile {
      if-feature "int-incremental-trace";
      presence
        "Enables the Integrity Protected Incremental Trace-Option.";
      description
        "This container describes the profile for the Integrity
         Protected Incremental Trace-Option.";

      uses ioam:ioam-incremental-tracing-profile;

      leaf int-method {
        when "derived-from-or-self(../node-action,
           'ioam:action-encapsulate')";
        type method-type;
        default "method-1";
        description
          "This object indicates the Integrity Protection Method for
           this profile.";
      }
    }

    container int-preallocated-tracing-profile {
      if-feature "int-preallocated-trace";
      presence
        "Enables the Integrity Protected Pre-allocated
         Trace-Option.";
      description
        "This container describes the profile for the Integrity
         Protected Pre-allocated Trace-Option.";

      uses ioam:ioam-preallocated-tracing-profile;

      leaf int-method {
        when "derived-from-or-self(../node-action,
           'ioam:action-encapsulate')";
        type method-type;
        default "method-1";
        description
          "This object indicates the Integrity Protection Method for
           this profile.";
      }
    }

    container int-pot-profile {
      if-feature "int-proof-of-transit";
      presence
        "Enables the Integrity Protected Proof of Transit Option.";
      description
        "This container describes the profile for the Integrity
         Protected Proof of Transit Option.";

      leaf use-namespace {
        type ioam:ioam-namespace;
        default "ioam:default-namespace";
        description
          "This object indicates the namespace used for the
           POT types.";
      }

      leaf pot-type {
        type ioam:ioam-pot-type;
        description
          "The type of a particular POT variant that specifies
           the POT data that is included.";
      }

      leaf node-action {
        type ioam:ioam-node-action;
        default "ioam:action-transit";
        description
          "This object indicates the action the node needs to
           take, e.g., encapsulation.";
      }

      leaf int-method {
        when "derived-from-or-self(../node-action,
           'ioam:action-encapsulate')";
        type method-type;
        default "method-1";
        description
          "This object indicates the Integrity Protection Method for
           this profile.";
      }
    }

    container int-e2e-profile {
      if-feature "int-edge-to-edge";
      presence
        "Enables the Integrity Protected Edge-to-Edge Option.";
      description
        "This container describes the profile for the Integrity
         Protected Edge-to-Edge Option.";

      uses ioam:ioam-e2e-profile;

      leaf int-method {
        when "derived-from-or-self(../node-action,
           'ioam:action-encapsulate')";
        type method-type;
        default "method-1";
        description
          "This object indicates the Integrity Protection Method for
           this profile.";
      }
    }
  }
}
